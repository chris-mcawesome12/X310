XYTRONIX-MIB DEFINITIONS ::= BEGIN

IMPORTS
        enterprises
                FROM RFC1155-SMI
        OBJECT-TYPE
                FROM RFC-1212
        DisplayString
                FROM RFC1213-MIB
        TRAP-TYPE
        		FROM RFC-1215;

xytronix	OBJECT IDENTIFIER ::= {enterprises 30586}
x300		OBJECT IDENTIFIER ::= {xytronix 10}
x301		OBJECT IDENTIFIER ::= {xytronix 11}
webswitch	OBJECT IDENTIFIER ::= {xytronix 12}
web10		OBJECT IDENTIFIER ::= {xytronix 13}
x320		OBJECT IDENTIFIER ::= {xytronix 14}
x332		OBJECT IDENTIFIER ::= {xytronix 15}
x320m		OBJECT IDENTIFIER ::= {xytronix 16}
x310		OBJECT IDENTIFIER ::= {xytronix 17}
x315		OBJECT IDENTIFIER ::= {xytronix 18}
-- x600m uses id 20
fiveinput OBJECT IDENTIFIER ::= {xytronix 21}
analogmodule OBJECT IDENTIFIER ::= {xytronix 22}

-- Entries for x300
x300TempOne OBJECT-TYPE
  SYNTAX  DisplayString
  ACCESS  read-only
  STATUS  mandatory
  DESCRIPTION
          "The temperature reading from sensor 1 on x300."
  ::= {x300 1}
  
x300TempTwo OBJECT-TYPE
  SYNTAX  DisplayString
  ACCESS  read-only
  STATUS  mandatory
  DESCRIPTION
          "The temperature reading from sensor 2 on x300."
  ::= {x300 2}
  
x300TempThree OBJECT-TYPE
  SYNTAX  DisplayString
  ACCESS  read-only
  STATUS  mandatory
  DESCRIPTION
          "The temperature reading from sensor 3 on x300."
  ::= {x300 3}
  
x300TempFour OBJECT-TYPE
  SYNTAX  DisplayString
  ACCESS  read-only
  STATUS  mandatory
  DESCRIPTION
          "The temperature reading from sensor 4 on x300."
  ::= {x300 4}
  
x300TempFive OBJECT-TYPE
  SYNTAX  DisplayString
  ACCESS  read-only
  STATUS  mandatory
  DESCRIPTION
          "The temperature reading from sensor 5 on x300."
  ::= {x300 5}
  
x300TempSix OBJECT-TYPE
  SYNTAX  DisplayString
  ACCESS  read-only
  STATUS  mandatory
  DESCRIPTION
          "The temperature reading from sensor 6 on x300."
  ::= {x300 6}
  
x300TempSeven OBJECT-TYPE
  SYNTAX  DisplayString
  ACCESS  read-only
  STATUS  mandatory
  DESCRIPTION
          "The temperature reading from sensor 7 on x300."
  ::= {x300 7}
  
x300TempEight OBJECT-TYPE
  SYNTAX  DisplayString
  ACCESS  read-only
  STATUS  mandatory
  DESCRIPTION
          "The temperature reading from sensor 8 on x300."
  ::= {x300 8}

x300RelayOne OBJECT-TYPE
  SYNTAX  DisplayString
  ACCESS  read-write
  STATUS  mandatory
  DESCRIPTION
          "Current state of relay one on x300."
  ::= {x300 11}
  
x300RelayTwo OBJECT-TYPE
  SYNTAX  DisplayString
  ACCESS  read-write
  STATUS  mandatory
  DESCRIPTION
          "Current state of relay two on x300."
  ::= {x300 12}
  
x300RelayThree OBJECT-TYPE
  SYNTAX  DisplayString
  ACCESS  read-write
  STATUS  mandatory
  DESCRIPTION
          "Current state of relay three on x300."
  ::= {x300 13} 
  
x300TempIndoor OBJECT-TYPE
  SYNTAX  DisplayString
  ACCESS  read-only
  STATUS  mandatory
  DESCRIPTION
          "The indoor temperature reading on x300."
  ::= {x300 16} 
  
x300TempOutdoor OBJECT-TYPE
  SYNTAX  DisplayString
  ACCESS  read-only
  STATUS  mandatory
  DESCRIPTION
          "The outdoor temperature reading on x300."
  ::= {x300 17} 

-- Entries for DUAL-EX
webrelayDualInputOne OBJECT-TYPE
  SYNTAX  DisplayString
  ACCESS  read-only
  STATUS  mandatory
  DESCRIPTION
          "Digital input 1."
  ::= {x301 1}
  
webrelayDualInputTwo OBJECT-TYPE
  SYNTAX  DisplayString
  ACCESS  read-only
  STATUS  mandatory
  DESCRIPTION
          "Digital input 2."
  ::= {x301 2}

webrelayDualRelayOne OBJECT-TYPE
  SYNTAX  DisplayString
  ACCESS  read-write
  STATUS  mandatory
  DESCRIPTION
          "Current state of relay one on WebRelay-Dual."
  ::= {x301 11}
  
webrelayDualRelayTwo OBJECT-TYPE
  SYNTAX  DisplayString
  ACCESS  read-write
  STATUS  mandatory
  DESCRIPTION
          "Current state of relay two on WebRelay-Dual."
  ::= {x301 12}
  
-- Entries for webswitch
webswitchInputOne OBJECT-TYPE
  SYNTAX  DisplayString
  ACCESS  read-only
  STATUS  mandatory
  DESCRIPTION
          "Digital input 1."
  ::= {webswitch 1}
  
webswitchInputTwo OBJECT-TYPE
  SYNTAX  DisplayString
  ACCESS  read-only
  STATUS  mandatory
  DESCRIPTION
          "Digital input 2."
  ::= {webswitch 2}

webswitchSensorOne OBJECT-TYPE
  SYNTAX  DisplayString
  ACCESS  read-only
  STATUS  mandatory
  DESCRIPTION
          "The sensor reading from sensor 1 on webswitch."
  ::= {webswitch 3}
  
webswitchSensorTwo OBJECT-TYPE
  SYNTAX  DisplayString
  ACCESS  read-only
  STATUS  mandatory
  DESCRIPTION
          "The sensor reading from sensor 2 on webswitch."
  ::= {webswitch 4}
  
webswitchSensorThree OBJECT-TYPE
  SYNTAX  DisplayString
  ACCESS  read-only
  STATUS  mandatory
  DESCRIPTION
          "The sensor reading from sensor 3 on webswitch."
  ::= {webswitch 5}

webswitchOutletOne OBJECT-TYPE
  SYNTAX  DisplayString
  ACCESS  read-write
  STATUS  mandatory
  DESCRIPTION
          "Current state of outlet one on webswitch."
  ::= {webswitch 11}
  
webswitchOutletTwo OBJECT-TYPE
  SYNTAX  DisplayString
  ACCESS  read-write
  STATUS  mandatory
  DESCRIPTION
          "Current state of outlet two on webswitch."
  ::= {webswitch 12}

webswitchOutletOneReboots OBJECT-TYPE
  SYNTAX  DisplayString
  ACCESS  read-write
  STATUS  mandatory
  DESCRIPTION
          "Reboot count for outlet 1."
  ::= {webswitch 101}
  
webswitchOutletTwoReboots OBJECT-TYPE
  SYNTAX  DisplayString
  ACCESS  read-write
  STATUS  mandatory
  DESCRIPTION
          "Reboot count for outlet 2."
  ::= {webswitch 102}

-- Entries for Webrelay 10
webrelayTenInputOne OBJECT-TYPE
  SYNTAX  DisplayString
  ACCESS  read-only
  STATUS  mandatory
  DESCRIPTION
          "Digital input 1."
  ::= {web10 1}
  
webrelayTenInputTwo OBJECT-TYPE
  SYNTAX  DisplayString
  ACCESS  read-only
  STATUS  mandatory
  DESCRIPTION
          "Digital input 2."
  ::= {web10 2}

webrelayTenSensorOne OBJECT-TYPE
  SYNTAX  DisplayString
  ACCESS  read-only
  STATUS  mandatory
  DESCRIPTION
          "Sensor 1 reading."
  ::= {web10 3}
  
webrelayTenSensorTwo OBJECT-TYPE
  SYNTAX  DisplayString
  ACCESS  read-only
  STATUS  mandatory
  DESCRIPTION
          "Sensor 2 reading."
  ::= {web10 4}
  
webrelayTenSensorThree OBJECT-TYPE
  SYNTAX  DisplayString
  ACCESS  read-only
  STATUS  mandatory
  DESCRIPTION
          "Sensor 3 reading."
  ::= {web10 5}

webrelayTenSensorFour OBJECT-TYPE
  SYNTAX  DisplayString
  ACCESS  read-only
  STATUS  mandatory
  DESCRIPTION
          "Sensor 4 reading."
  ::= {web10 6}
  
webrelayTenSensorFive OBJECT-TYPE
  SYNTAX  DisplayString
  ACCESS  read-only
  STATUS  mandatory
  DESCRIPTION
          "Sensor 5 reading."
  ::= {web10 7}
  
webrelayTenSensorSix OBJECT-TYPE
  SYNTAX  DisplayString
  ACCESS  read-only
  STATUS  mandatory
  DESCRIPTION
          "Sensor 6 reading."
  ::= {web10 8}

webrelayTenSensorSeven OBJECT-TYPE
  SYNTAX  DisplayString
  ACCESS  read-only
  STATUS  mandatory
  DESCRIPTION
          "Sensor 7 reading."
  ::= {web10 9}
  
webrelayTenSensorEight OBJECT-TYPE
  SYNTAX  DisplayString
  ACCESS  read-only
  STATUS  mandatory
  DESCRIPTION
          "Sensor 8 reading."
  ::= {web10 10}
  
webrelayTenRelayOne OBJECT-TYPE
  SYNTAX  DisplayString
  ACCESS  read-write
  STATUS  mandatory
  DESCRIPTION
          "Current state of relay one on WebRelay-10."
  ::= {web10 11}
  
webrelayTenRelayTwo OBJECT-TYPE
  SYNTAX  DisplayString
  ACCESS  read-write
  STATUS  mandatory
  DESCRIPTION
          "Current state of relay two on WebRelay-10."
  ::= {web10 12}
  
webrelayTenRelayThree OBJECT-TYPE
  SYNTAX  DisplayString
  ACCESS  read-write
  STATUS  mandatory
  DESCRIPTION
          "Current state of relay three on WebRelay-10."
  ::= {web10 13}
  
webrelayTenRelayFour OBJECT-TYPE
  SYNTAX  DisplayString
  ACCESS  read-write
  STATUS  mandatory
  DESCRIPTION
          "Current state of relay four on WebRelay-10."
  ::= {web10 14}
  
webrelayTenRelayFive OBJECT-TYPE
  SYNTAX  DisplayString
  ACCESS  read-write
  STATUS  mandatory
  DESCRIPTION
          "Current state of relay five on WebRelay-10."
  ::= {web10 15}
  
webrelayTenRelaySix OBJECT-TYPE
  SYNTAX  DisplayString
  ACCESS  read-write
  STATUS  mandatory
  DESCRIPTION
          "Current state of relay six on WebRelay-10."
  ::= {web10 16}
  
webrelayTenRelaySeven OBJECT-TYPE
  SYNTAX  DisplayString
  ACCESS  read-write
  STATUS  mandatory
  DESCRIPTION
          "Current state of relay seven on WebRelay-10."
  ::= {web10 17}
  
webrelayTenRelayEight OBJECT-TYPE
  SYNTAX  DisplayString
  ACCESS  read-write
  STATUS  mandatory
  DESCRIPTION
          "Current state of relay eight on WebRelay-10."
  ::= {web10 18}
  
webrelayTenRelayNine OBJECT-TYPE
  SYNTAX  DisplayString
  ACCESS  read-write
  STATUS  mandatory
  DESCRIPTION
          "Current state of relay nine on WebRelay-10."
  ::= {web10 19}
  
webrelayTenRelayTen OBJECT-TYPE
  SYNTAX  DisplayString
  ACCESS  read-write
  STATUS  mandatory
  DESCRIPTION
          "Current state of relay ten on WebRelay-10."
  ::= {web10 20}

webrelayTenSensorNine OBJECT-TYPE
  SYNTAX  DisplayString
  ACCESS  read-only
  STATUS  mandatory
  DESCRIPTION
          "Sensor 9 reading."
  ::= {web10 21}
  
webrelayTenSensorTen OBJECT-TYPE
  SYNTAX  DisplayString
  ACCESS  read-only
  STATUS  mandatory
  DESCRIPTION
          "Sensor 10 reading."
  ::= {web10 22}
  
-- Entries for x320
x320InputOne OBJECT-TYPE
  SYNTAX  DisplayString
  ACCESS  read-only
  STATUS  mandatory
  DESCRIPTION
          "Digital input 1."
  ::= {x320 1}
  
x320InputTwo OBJECT-TYPE
  SYNTAX  DisplayString
  ACCESS  read-only
  STATUS  mandatory
  DESCRIPTION
          "Digital input 2."
  ::= {x320 2}
  
x320InputThree OBJECT-TYPE
  SYNTAX  DisplayString
  ACCESS  read-only
  STATUS  mandatory
  DESCRIPTION
          "Digital input 3."
  ::= {x320 3}  
  
x320InputFour OBJECT-TYPE
  SYNTAX  DisplayString
  ACCESS  read-only
  STATUS  mandatory
  DESCRIPTION
          "Digital input 4."
  ::= {x320 4}
  
x320InputFive OBJECT-TYPE
  SYNTAX  DisplayString
  ACCESS  read-only
  STATUS  mandatory
  DESCRIPTION
          "Digital input 5."
  ::= {x320 5}
  
x320InputSix OBJECT-TYPE
  SYNTAX  DisplayString
  ACCESS  read-only
  STATUS  mandatory
  DESCRIPTION
          "Digital input 6."
  ::= {x320 6}

x320SensorOne OBJECT-TYPE
  SYNTAX  DisplayString
  ACCESS  read-only
  STATUS  mandatory
  DESCRIPTION
          "The sensor reading from sensor 1 on x320."
  ::= {x320 8}
  
x320SensorTwo OBJECT-TYPE
  SYNTAX  DisplayString
  ACCESS  read-only
  STATUS  mandatory
  DESCRIPTION
          "The sensor reading from sensor 2 on x320."
  ::= {x320 9}
  
x320SensorThree OBJECT-TYPE
  SYNTAX  DisplayString
  ACCESS  read-only
  STATUS  mandatory
  DESCRIPTION
          "The sensor reading from sensor 3 on x320."
  ::= {x320 10}

x320SensorFour OBJECT-TYPE
  SYNTAX  DisplayString
  ACCESS  read-only
  STATUS  mandatory
  DESCRIPTION
          "The sensor reading from sensor 4 on x320."
  ::= {x320 11}
  
x320SensorFive OBJECT-TYPE
  SYNTAX  DisplayString
  ACCESS  read-only
  STATUS  mandatory
  DESCRIPTION
          "The sensor reading from sensor 5 on x320."
  ::= {x320 12}
  
x320SensorSix OBJECT-TYPE
  SYNTAX  DisplayString
  ACCESS  read-only
  STATUS  mandatory
  DESCRIPTION
          "The sensor reading from sensor 6 on x320."
  ::= {x320 13}  

x320OutputOne OBJECT-TYPE
  SYNTAX  DisplayString
  ACCESS  read-write
  STATUS  mandatory
  DESCRIPTION
          "Current state of output one on x320."
  ::= {x320 14}
  
x320OutputTwo OBJECT-TYPE
  SYNTAX  DisplayString
  ACCESS  read-write
  STATUS  mandatory
  DESCRIPTION
          "Current state of output two on x320."
  ::= {x320 15}

x320AnalogOne OBJECT-TYPE
  SYNTAX  DisplayString
  ACCESS  read-only
  STATUS  mandatory
  DESCRIPTION
          "Analog input 1 on x320."
  ::= {x320 17}
  
x320AnalogTwo OBJECT-TYPE
  SYNTAX  DisplayString
  ACCESS  read-only
  STATUS  mandatory
  DESCRIPTION
          "Analog input 2 on x320."
  ::= {x320 18}
  
x320AnalogThree OBJECT-TYPE
  SYNTAX  DisplayString
  ACCESS  read-only
  STATUS  mandatory
  DESCRIPTION
          "Analog input 3 on x320."
  ::= {x320 19}
  
x320AnalogFour OBJECT-TYPE
  SYNTAX  DisplayString
  ACCESS  read-only
  STATUS  mandatory
  DESCRIPTION
          "Analog input 4 on x320."
  ::= {x320 20}
  
x320PulseCounterOne OBJECT-TYPE
  SYNTAX  DisplayString
  ACCESS  read-only
  STATUS  mandatory
  DESCRIPTION
          "Pulse Counter 1 on x320."
  ::= {x320 21}
  
x320PulseCounterTwo OBJECT-TYPE
  SYNTAX  DisplayString
  ACCESS  read-only
  STATUS  mandatory
  DESCRIPTION
          "PulseCounter 2 on x320."
  ::= {x320 22}
  
x320Frequency OBJECT-TYPE
  SYNTAX  DisplayString
  ACCESS  read-only
  STATUS  mandatory
  DESCRIPTION
          "Frequency input on x320."
  ::= {x320 23}
  
x320PulseRateOne OBJECT-TYPE
  SYNTAX  DisplayString
  ACCESS  read-only
  STATUS  mandatory
  DESCRIPTION
          "Pulse Rate 1 on x320."
  ::= {x320 24}
  
x320PulseRateTwo OBJECT-TYPE
  SYNTAX  DisplayString
  ACCESS  read-only
  STATUS  mandatory
  DESCRIPTION
          "Pulse Rate 2 on x320."
  ::= {x320 25}
  
x320Vin OBJECT-TYPE
  SYNTAX  DisplayString
  ACCESS  read-only
  STATUS  mandatory
  DESCRIPTION
          "Vin on x320."
  ::= {x320 27}


-- Entries for x332
x332InputOne OBJECT-TYPE
  SYNTAX  DisplayString
  ACCESS  read-only
  STATUS  mandatory
  DESCRIPTION
          "Digital input 1."
  ::= {x332 1}
  
x332InputTwo OBJECT-TYPE
  SYNTAX  DisplayString
  ACCESS  read-only
  STATUS  mandatory
  DESCRIPTION
          "Digital input 2."
  ::= {x332 2}
  
x332InputThree OBJECT-TYPE
  SYNTAX  DisplayString
  ACCESS  read-only
  STATUS  mandatory
  DESCRIPTION
          "Digital input 3."
  ::= {x332 3}

x332InputFour OBJECT-TYPE
  SYNTAX  DisplayString
  ACCESS  read-only
  STATUS  mandatory
  DESCRIPTION
          "Digital input 4."
  ::= {x332 4}
  
x332InputFive OBJECT-TYPE
  SYNTAX  DisplayString
  ACCESS  read-only
  STATUS  mandatory
  DESCRIPTION
          "Digital input 5."
  ::= {x332 5}
  
x332InputSix OBJECT-TYPE
  SYNTAX  DisplayString
  ACCESS  read-only
  STATUS  mandatory
  DESCRIPTION
          "Digital input 6."
  ::= {x332 6}

x332InputSeven OBJECT-TYPE
  SYNTAX  DisplayString
  ACCESS  read-only
  STATUS  mandatory
  DESCRIPTION
          "Digital input 7."
  ::= {x332 7}
  
x332InputEight OBJECT-TYPE
  SYNTAX  DisplayString
  ACCESS  read-only
  STATUS  mandatory
  DESCRIPTION
          "Digital input 8."
  ::= {x332 8}
  
x332InputNine OBJECT-TYPE
  SYNTAX  DisplayString
  ACCESS  read-only
  STATUS  mandatory
  DESCRIPTION
          "Digital input 9."
  ::= {x332 9}
  
x332InputTen OBJECT-TYPE
  SYNTAX  DisplayString
  ACCESS  read-only
  STATUS  mandatory
  DESCRIPTION
          "Digital input 10."
  ::= {x332 10}
  
x332InputEleven OBJECT-TYPE
  SYNTAX  DisplayString
  ACCESS  read-only
  STATUS  mandatory
  DESCRIPTION
          "Digital input 11."
  ::= {x332 11}
  
x332InputTwelve OBJECT-TYPE
  SYNTAX  DisplayString
  ACCESS  read-only
  STATUS  mandatory
  DESCRIPTION
          "Digital input 12."
  ::= {x332 12}
  
x332InputThriteen OBJECT-TYPE
  SYNTAX  DisplayString
  ACCESS  read-only
  STATUS  mandatory
  DESCRIPTION
          "Digital input 13."
  ::= {x332 13}
  
x332InputFourteen OBJECT-TYPE
  SYNTAX  DisplayString
  ACCESS  read-only
  STATUS  mandatory
  DESCRIPTION
          "Digital input 14."
  ::= {x332 14}
  
x332InputFifteen OBJECT-TYPE
  SYNTAX  DisplayString
  ACCESS  read-only
  STATUS  mandatory
  DESCRIPTION
          "Digital input 15."
  ::= {x332 15}
  
x332InputSixteen OBJECT-TYPE
  SYNTAX  DisplayString
  ACCESS  read-only
  STATUS  mandatory
  DESCRIPTION
          "Digital input 16."
  ::= {x332 16}
  
x332InputSeventeen OBJECT-TYPE
  SYNTAX  DisplayString
  ACCESS  read-only
  STATUS  mandatory
  DESCRIPTION
          "Digital input 17."
  ::= {x332 17}

x332InputEighteen OBJECT-TYPE
  SYNTAX  DisplayString
  ACCESS  read-only
  STATUS  mandatory
  DESCRIPTION
          "Digital input 18."
  ::= {x332 18}

x332SensorOne OBJECT-TYPE
  SYNTAX  DisplayString
  ACCESS  read-only
  STATUS  mandatory
  DESCRIPTION
          "The sensor reading from sensor 1."
  ::= {x332 20}
  
x332SensorTwo OBJECT-TYPE
  SYNTAX  DisplayString
  ACCESS  read-only
  STATUS  mandatory
  DESCRIPTION
          "The sensor reading from sensor 2."
  ::= {x332 21}
  
x332SensorThree OBJECT-TYPE
  SYNTAX  DisplayString
  ACCESS  read-only
  STATUS  mandatory
  DESCRIPTION
          "The sensor reading from sensor 3."
  ::= {x332 22}
  
x332SensorFour OBJECT-TYPE
  SYNTAX  DisplayString
  ACCESS  read-only
  STATUS  mandatory
  DESCRIPTION
          "The sensor reading from sensor 4."
  ::= {x332 23}

x332RelayOne OBJECT-TYPE
  SYNTAX  DisplayString
  ACCESS  read-write
  STATUS  mandatory
  DESCRIPTION
          "Current state of relay 1."
  ::= {x332 30}
  
x332RelayTwo OBJECT-TYPE
  SYNTAX  DisplayString
  ACCESS  read-write
  STATUS  mandatory
  DESCRIPTION
          "Current state of relay 2."
  ::= {x332 31}  
  
x332RelayThree OBJECT-TYPE
  SYNTAX  DisplayString
  ACCESS  read-write
  STATUS  mandatory
  DESCRIPTION
          "Current state of relay 3."
  ::= {x332 32}
  
x332RelayFour OBJECT-TYPE
  SYNTAX  DisplayString
  ACCESS  read-write
  STATUS  mandatory
  DESCRIPTION
          "Current state of relay 4."
  ::= {x332 33}
  
x332RelayFive OBJECT-TYPE
  SYNTAX  DisplayString
  ACCESS  read-write
  STATUS  mandatory
  DESCRIPTION
          "Current state of relay 5."
  ::= {x332 34}
  
x332RelaySix OBJECT-TYPE
  SYNTAX  DisplayString
  ACCESS  read-write
  STATUS  mandatory
  DESCRIPTION
          "Current state of relay 6."
  ::= {x332 35}
  
x332RelaySeven OBJECT-TYPE
  SYNTAX  DisplayString
  ACCESS  read-write
  STATUS  mandatory
  DESCRIPTION
          "Current state of relay 7."
  ::= {x332 36}
  
x332RelayEight OBJECT-TYPE
  SYNTAX  DisplayString
  ACCESS  read-write
  STATUS  mandatory
  DESCRIPTION
          "Current state of relay 8."
  ::= {x332 37}
  
x332RelayNine OBJECT-TYPE
  SYNTAX  DisplayString
  ACCESS  read-write
  STATUS  mandatory
  DESCRIPTION
          "Current state of relay 9."
  ::= {x332 38}
  
x332RelayTen OBJECT-TYPE
  SYNTAX  DisplayString
  ACCESS  read-write
  STATUS  mandatory
  DESCRIPTION
          "Current state of relay 10."
  ::= {x332 39}
  
x332RelayEleven OBJECT-TYPE
  SYNTAX  DisplayString
  ACCESS  read-write
  STATUS  mandatory
  DESCRIPTION
          "Current state of relay 11."
  ::= {x332 40}
  
x332RelayTwelve OBJECT-TYPE
  SYNTAX  DisplayString
  ACCESS  read-write
  STATUS  mandatory
  DESCRIPTION
          "Current state of relay 12."
  ::= {x332 41}
  
x332RelayThirteen OBJECT-TYPE
  SYNTAX  DisplayString
  ACCESS  read-write
  STATUS  mandatory
  DESCRIPTION
          "Current state of relay 13."
  ::= {x332 42}
  
x332RelayFourteen OBJECT-TYPE
  SYNTAX  DisplayString
  ACCESS  read-write
  STATUS  mandatory
  DESCRIPTION
          "Current state of relay 14."
  ::= {x332 43}
  
x332RelayFifteen OBJECT-TYPE
  SYNTAX  DisplayString
  ACCESS  read-write
  STATUS  mandatory
  DESCRIPTION
          "Current state of relay 15."
  ::= {x332 44}
  
x332RelaySixteen OBJECT-TYPE
  SYNTAX  DisplayString
  ACCESS  read-write
  STATUS  mandatory
  DESCRIPTION
          "Current state of relay 16."
  ::= {x332 45}

x332AnalogOne OBJECT-TYPE
  SYNTAX  DisplayString
  ACCESS  read-only
  STATUS  mandatory
  DESCRIPTION
          "Analog input 1."
  ::= {x332 50}
  
x332AnalogTwo OBJECT-TYPE
  SYNTAX  DisplayString
  ACCESS  read-only
  STATUS  mandatory
  DESCRIPTION
          "Analog input 2."
  ::= {x332 51}
  
x332AnalogThree OBJECT-TYPE
  SYNTAX  DisplayString
  ACCESS  read-only
  STATUS  mandatory
  DESCRIPTION
          "Analog input 3."
  ::= {x332 52}
  
x332AnalogFour OBJECT-TYPE
  SYNTAX  DisplayString
  ACCESS  read-only
  STATUS  mandatory
  DESCRIPTION
          "Analog input 4."
  ::= {x332 53}
  
x332CounterOne OBJECT-TYPE
  SYNTAX  DisplayString
  ACCESS  read-only
  STATUS  mandatory
  DESCRIPTION
          "Counter 1."
  ::= {x332 60}
  
x332CounterTwo OBJECT-TYPE
  SYNTAX  DisplayString
  ACCESS  read-only
  STATUS  mandatory
  DESCRIPTION
          "Counter 2."
  ::= {x332 61}

-- Entries for x320m

x320mWindSpeed OBJECT-TYPE
  SYNTAX  DisplayString
  ACCESS  read-only
  STATUS  mandatory
  DESCRIPTION
          "Wind Speed."
  ::= {x320m 1}
  
x320mWindDirection OBJECT-TYPE
  SYNTAX  DisplayString
  ACCESS  read-only
  STATUS  mandatory
  DESCRIPTION
          "Wind Direction."
  ::= {x320m 2}
  
x320mRainTotal OBJECT-TYPE
  SYNTAX  DisplayString
  ACCESS  read-only
  STATUS  mandatory
  DESCRIPTION
          "Rain Total Since Reset."
  ::= {x320m 3}

x320mTemperature OBJECT-TYPE
  SYNTAX  DisplayString
  ACCESS  read-only
  STATUS  mandatory
  DESCRIPTION
          "Temperature."
  ::= {x320m 4}
  
x320mHumidity OBJECT-TYPE
  SYNTAX  DisplayString
  ACCESS  read-only
  STATUS  mandatory
  DESCRIPTION
          "Humidity."
  ::= {x320m 5}
  
x320mSolarRadiation OBJECT-TYPE
  SYNTAX  DisplayString
  ACCESS  read-only
  STATUS  mandatory
  DESCRIPTION
          "Solor Radiation."
  ::= {x320m 6}
  
x320mBarPressure OBJECT-TYPE
  SYNTAX  DisplayString
  ACCESS  read-only
  STATUS  mandatory
  DESCRIPTION
          "Barometric Pressure."
  ::= {x320m 7}
  
x320mAux1 OBJECT-TYPE
  SYNTAX  DisplayString
  ACCESS  read-only
  STATUS  mandatory
  DESCRIPTION
          "Auxiliary 1."
  ::= {x320m 8}
  
x320mAux2 OBJECT-TYPE
  SYNTAX  DisplayString
  ACCESS  read-only
  STATUS  mandatory
  DESCRIPTION
          "Auxiliary 2."
  ::= {x320m 9}  
  
x320mGustSpeed OBJECT-TYPE
  SYNTAX  DisplayString
  ACCESS  read-only
  STATUS  mandatory
  DESCRIPTION
          "Wind Gust Speed."
  ::= {x320m 10}
  
x320mGustDirection OBJECT-TYPE
  SYNTAX  DisplayString
  ACCESS  read-only
  STATUS  mandatory
  DESCRIPTION
          "Wind Gust Direction."
  ::= {x320m 11}
  
x320mRainPastHour OBJECT-TYPE
  SYNTAX  DisplayString
  ACCESS  read-only
  STATUS  mandatory
  DESCRIPTION
          "Rain Past Hour."
  ::= {x320m 12}
  
x320mRainToday OBJECT-TYPE
  SYNTAX  DisplayString
  ACCESS  read-only
  STATUS  mandatory
  DESCRIPTION
          "Rain Today."
  ::= {x320m 13}
  
x320mRainPrev7Days OBJECT-TYPE
  SYNTAX  DisplayString
  ACCESS  read-only
  STATUS  mandatory
  DESCRIPTION
          "Rain Previous 7 Days."
  ::= {x320m 14}

x320mTempHigh OBJECT-TYPE
  SYNTAX  DisplayString
  ACCESS  read-only
  STATUS  mandatory
  DESCRIPTION
          "Today's High Temperature."
  ::= {x320m 15}
  
x320mTempLow OBJECT-TYPE
  SYNTAX  DisplayString
  ACCESS  read-only
  STATUS  mandatory
  DESCRIPTION
          "Today's Low Temperature."
  ::= {x320m 16}
  
x320mTempHighY OBJECT-TYPE
  SYNTAX  DisplayString
  ACCESS  read-only
  STATUS  mandatory
  DESCRIPTION
          "Yesterday's High Temperature."
  ::= {x320m 17}
  
x320mTempLowY OBJECT-TYPE
  SYNTAX  DisplayString
  ACCESS  read-only
  STATUS  mandatory
  DESCRIPTION
          "Yesterday's Low Temperature."
  ::= {x320m 18}
  
x320mHeatIndex OBJECT-TYPE
  SYNTAX  DisplayString
  ACCESS  read-only
  STATUS  mandatory
  DESCRIPTION
          "Heat Index."
  ::= {x320m 19}
  
x320mWindChill OBJECT-TYPE
  SYNTAX  DisplayString
  ACCESS  read-only
  STATUS  mandatory
  DESCRIPTION
          "Wind Chill."
  ::= {x320m 20}
  
x320mDewPoint OBJECT-TYPE
  SYNTAX  DisplayString
  ACCESS  read-only
  STATUS  mandatory
  DESCRIPTION
          "Dew Point."
  ::= {x320m 21}
  
x320mHumidityHigh OBJECT-TYPE
  SYNTAX  DisplayString
  ACCESS  read-only
  STATUS  mandatory
  DESCRIPTION
          "Today's High Humidity."
  ::= {x320m 22}
  
x320mHumidityLow OBJECT-TYPE
  SYNTAX  DisplayString
  ACCESS  read-only
  STATUS  mandatory
  DESCRIPTION
          "Today's Low Humidity."
  ::= {x320m 23}
  
x320mHumidityHighY OBJECT-TYPE
  SYNTAX  DisplayString
  ACCESS  read-only
  STATUS  mandatory
  DESCRIPTION
          "Yesterday's High Humidity."
  ::= {x320m 24}
  
x320mHumidityLowY OBJECT-TYPE
  SYNTAX  DisplayString
  ACCESS  read-only
  STATUS  mandatory
  DESCRIPTION
          "Yesterday's Low Humidity."
  ::= {x320m 25}


-- Entries for x310
x310InputOne OBJECT-TYPE
  SYNTAX  DisplayString
  ACCESS  read-only
  STATUS  mandatory
  DESCRIPTION
          "Digital input 1."
  ::= {x310 1}
  
x310InputTwo OBJECT-TYPE
  SYNTAX  DisplayString
  ACCESS  read-only
  STATUS  mandatory
  DESCRIPTION
          "Digital input 2."
  ::= {x310 2}
  
x310InputThree OBJECT-TYPE
  SYNTAX  DisplayString
  ACCESS  read-only
  STATUS  mandatory
  DESCRIPTION
          "Digital input 3."
  ::= {x310 3}

x310InputFour OBJECT-TYPE
  SYNTAX  DisplayString
  ACCESS  read-only
  STATUS  mandatory
  DESCRIPTION
          "Digital input 4."
  ::= {x310 4}
  
x310SensorOne OBJECT-TYPE
  SYNTAX  DisplayString
  ACCESS  read-only
  STATUS  mandatory
  DESCRIPTION
          "The sensor reading from sensor 1."
  ::= {x310 20}
  
x310SensorTwo OBJECT-TYPE
  SYNTAX  DisplayString
  ACCESS  read-only
  STATUS  mandatory
  DESCRIPTION
          "The sensor reading from sensor 2."
  ::= {x310 21}
  
x310SensorThree OBJECT-TYPE
  SYNTAX  DisplayString
  ACCESS  read-only
  STATUS  mandatory
  DESCRIPTION
          "The sensor reading from sensor 3."
  ::= {x310 22}
  
x310SensorFour OBJECT-TYPE
  SYNTAX  DisplayString
  ACCESS  read-only
  STATUS  mandatory
  DESCRIPTION
          "The sensor reading from sensor 4."
  ::= {x310 23}

x310RelayOne OBJECT-TYPE
  SYNTAX  DisplayString
  ACCESS  read-write
  STATUS  mandatory
  DESCRIPTION
          "Current state of relay 1."
  ::= {x310 30}
  
x310RelayTwo OBJECT-TYPE
  SYNTAX  DisplayString
  ACCESS  read-write
  STATUS  mandatory
  DESCRIPTION
          "Current state of relay 2."
  ::= {x310 31}  
  
x310RelayThree OBJECT-TYPE
  SYNTAX  DisplayString
  ACCESS  read-write
  STATUS  mandatory
  DESCRIPTION
          "Current state of relay 3."
  ::= {x310 32}
  
x310RelayFour OBJECT-TYPE
  SYNTAX  DisplayString
  ACCESS  read-write
  STATUS  mandatory
  DESCRIPTION
          "Current state of relay 4."
  ::= {x310 33}
  
x310Vin OBJECT-TYPE
  SYNTAX  DisplayString
  ACCESS  read-only
  STATUS  mandatory
  DESCRIPTION
          "Vin"
  ::= {x310 50}
  

x310CounterOne OBJECT-TYPE
  SYNTAX  DisplayString
  ACCESS  read-only
  STATUS  mandatory
  DESCRIPTION
          "Counter 1."
  ::= {x310 60}
  
x310CounterTwo OBJECT-TYPE
  SYNTAX  DisplayString
  ACCESS  read-only
  STATUS  mandatory
  DESCRIPTION
          "Counter 2."
  ::= {x310 61}  
 
 
 -- Entries for Five Input Moduel
fiveinputInputOne OBJECT-TYPE
  SYNTAX  DisplayString
  ACCESS  read-only
  STATUS  mandatory
  DESCRIPTION
          "Digital input 1."
  ::= {fiveinput 1}
  
 fiveinputInputTwo OBJECT-TYPE
  SYNTAX  DisplayString
  ACCESS  read-only
  STATUS  mandatory
  DESCRIPTION
          "Digital input 2."
  ::= {fiveinput 2}
  
 fiveinputInputThree OBJECT-TYPE
  SYNTAX  DisplayString
  ACCESS  read-only
  STATUS  mandatory
  DESCRIPTION
          "Digital input 3."
  ::= {fiveinput 3}
  
 fiveinputInputFour OBJECT-TYPE
  SYNTAX  DisplayString
  ACCESS  read-only
  STATUS  mandatory
  DESCRIPTION
          "Digital input 4."
  ::= {fiveinput 4}
  
 fiveinputInputFive OBJECT-TYPE
  SYNTAX  DisplayString
  ACCESS  read-only
  STATUS  mandatory
  DESCRIPTION
          "Digital input 5."
  ::= {fiveinput 5}  

  -- Entries for the analog module
 analogModuleAnalogOne OBJECT-TYPE
  SYNTAX  DisplayString
  ACCESS  read-only
  STATUS  mandatory
  DESCRIPTION
          "Analog input 1 on Analog Module."
  ::= {analogmodule 1}
  
 analogModuleAnalogTwo OBJECT-TYPE
  SYNTAX  DisplayString
  ACCESS  read-only
  STATUS  mandatory
  DESCRIPTION
          "Analog input 2 on Analog Module."
  ::= {analogmodule 2}
  
 analogModuleAnalogThree OBJECT-TYPE
  SYNTAX  DisplayString
  ACCESS  read-only
  STATUS  mandatory
  DESCRIPTION
          "Analog input 3 on Analog Module."
  ::= {analogmodule 3}
  
 analogModuleAnalogFour OBJECT-TYPE
  SYNTAX  DisplayString
  ACCESS  read-only
  STATUS  mandatory
  DESCRIPTION
          "Analog input 4 on Analog Module."
  ::= {analogmodule 4}
  
 analogModuleAnalogFive OBJECT-TYPE
  SYNTAX  DisplayString
  ACCESS  read-only
  STATUS  mandatory
  DESCRIPTION
          "Analog input 5 on Analog Module."
  ::= {analogmodule 5}
  
 analogModuleAnalogSix OBJECT-TYPE
  SYNTAX  DisplayString
  ACCESS  read-only
  STATUS  mandatory
  DESCRIPTION
          "Analog input 6 on Analog Module."
  ::= {analogmodule 6}
  
 analogModuleAnalogSeven OBJECT-TYPE
  SYNTAX  DisplayString
  ACCESS  read-only
  STATUS  mandatory
  DESCRIPTION
          "Analog input 7 on Analog Module."
  ::= {analogmodule 7}
  
 analogModuleAnalogEight OBJECT-TYPE
  SYNTAX  DisplayString
  ACCESS  read-only
  STATUS  mandatory
  DESCRIPTION
          "Analog input 8 on Analog Module."
  ::= {analogmodule 8}
  
-- Traps

sensorOne TRAP-TYPE
	ENTERPRISE xytronix	
	DESCRIPTION
					"Sensor one alarm ."
	::= 65
	
sensorTwo TRAP-TYPE
	ENTERPRISE xytronix
	DESCRIPTION
					"Sensor two alarm."
	::= 66
	
sensorThree TRAP-TYPE
	ENTERPRISE xytronix
	DESCRIPTION
					"Sensor three alarm."
	::= 67
	
sensorFour TRAP-TYPE
	ENTERPRISE xytronix
	DESCRIPTION
					"Sensor four alarm."
	::= 68
	
sensorFive TRAP-TYPE
	ENTERPRISE xytronix
	DESCRIPTION
					"Sensor five alarm."
	::= 69
	
sensorSix TRAP-TYPE
	ENTERPRISE xytronix
	DESCRIPTION
					"Sensor six alarm."
	::= 70
	
sensorSeven TRAP-TYPE
	ENTERPRISE xytronix
	DESCRIPTION
					"Sensor seven alarm."
	::= 71
	
sensorEight TRAP-TYPE
	ENTERPRISE xytronix
	DESCRIPTION
					"Sensor eight alarm."
	::= 72

relayOneStateChange TRAP-TYPE
	ENTERPRISE xytronix
	DESCRIPTION
					"Relay one state change."
	::= 75
	
relayTwoStateChange TRAP-TYPE
	ENTERPRISE xytronix
	DESCRIPTION
					"Relay two state change."
	::= 76
	
relayThreeStateChange TRAP-TYPE
	ENTERPRISE xytronix
	DESCRIPTION
					"Relay three state change."
	::= 77
	
relayFourStateChange TRAP-TYPE
	ENTERPRISE xytronix
	DESCRIPTION
					"Relay four state change."
	::= 78
	
relayFiveStateChange TRAP-TYPE
	ENTERPRISE xytronix
	DESCRIPTION
					"Relay five state change."
	::= 79
	
relaySixStateChange TRAP-TYPE
	ENTERPRISE xytronix
	DESCRIPTION
					"Relay six state change."
	::= 80
	
relaySevenStateChange TRAP-TYPE
	ENTERPRISE xytronix
	DESCRIPTION
					"Relay seven state change."
	::= 81
	
relayEightStateChange TRAP-TYPE
	ENTERPRISE xytronix
	DESCRIPTION
					"Relay eight state change."
	::= 82
	
relayNineStateChange TRAP-TYPE
	ENTERPRISE xytronix
	DESCRIPTION
					"Relay nine state change."
	::= 83
	
relayTenStateChange TRAP-TYPE
	ENTERPRISE xytronix
	DESCRIPTION
					"Relay ten state change."
	::= 84
	
relayElevenStateChange TRAP-TYPE
	ENTERPRISE xytronix
	DESCRIPTION
					"Relay eleven state change."
	::= 85
	
relayTwelveStateChange TRAP-TYPE
	ENTERPRISE xytronix
	DESCRIPTION
					"Relay twelve state change."
	::= 86
	
relayThirteenStateChange TRAP-TYPE
	ENTERPRISE xytronix
	DESCRIPTION
					"Relay thirteen state change."
	::= 87
	
relayFourteenStateChange TRAP-TYPE
	ENTERPRISE xytronix
	DESCRIPTION
					"Relay fourteen state change."
	::= 88

relayFifteenStateChange TRAP-TYPE
	ENTERPRISE xytronix
	DESCRIPTION
					"Relay fifteen state change."
	::= 89
	
relaySixteenStateChange TRAP-TYPE
	ENTERPRISE xytronix
	DESCRIPTION
					"Relay sixteen state change."
	::= 90

inputOneChange TRAP-TYPE
	ENTERPRISE xytronix
	DESCRIPTION
					"Input one state change."
	::= 95
	
inputTwoChange TRAP-TYPE
	ENTERPRISE xytronix
	DESCRIPTION
					"Input two state change."
	::= 96
	
inputThreeChange TRAP-TYPE
	ENTERPRISE xytronix
	DESCRIPTION
					"Input three state change."
	::= 97	
	
inputFourChange TRAP-TYPE
	ENTERPRISE xytronix
	DESCRIPTION
					"Input four state change."
	::= 98
	
inputFiveChange TRAP-TYPE
	ENTERPRISE xytronix
	DESCRIPTION
					"Input five state change."
	::= 99
	
inputSixChange TRAP-TYPE
	ENTERPRISE xytronix
	DESCRIPTION
					"Input six state change."
	::= 100
	
inputSevenChange TRAP-TYPE
	ENTERPRISE xytronix
	DESCRIPTION
					"Input seven state change."
	::= 101
	
inputEightChange TRAP-TYPE
	ENTERPRISE xytronix
	DESCRIPTION
					"Input eight state change."
	::= 102
	
inputNineChange TRAP-TYPE
	ENTERPRISE xytronix
	DESCRIPTION
					"Input nine state change."
	::= 103
	
inputTenChange TRAP-TYPE
	ENTERPRISE xytronix
	DESCRIPTION
					"Input ten state change."
	::= 104
	
inputElevenChange TRAP-TYPE
	ENTERPRISE xytronix
	DESCRIPTION
					"Input eleven state change."
	::= 105
	
inputTwelveChange TRAP-TYPE
	ENTERPRISE xytronix
	DESCRIPTION
					"Input twelve state change."
	::= 106
	
inputThirteenChange TRAP-TYPE
	ENTERPRISE xytronix
	DESCRIPTION
					"Input thirteen state change."
	::= 107
	
inputFourteenChange TRAP-TYPE
	ENTERPRISE xytronix
	DESCRIPTION
					"Input fourteen state change."
	::= 108
	
inputFifteenChange TRAP-TYPE
	ENTERPRISE xytronix
	DESCRIPTION
					"Input fifteen state change."
	::= 109
	
inputSixteenChange TRAP-TYPE
	ENTERPRISE xytronix
	DESCRIPTION
					"Input sixteen state change."
	::= 110
	
inputSeventeenChange TRAP-TYPE
	ENTERPRISE xytronix
	DESCRIPTION
					"Input seventeen state change."
	::= 111
	
inputEighteenChange TRAP-TYPE
	ENTERPRISE xytronix
	DESCRIPTION
					"Input eighteen state change."
	::= 112
	
outletOneReboot TRAP-TYPE
	ENTERPRISE xytronix
	DESCRIPTION
					"Outlet one reboot."
	::= 115
	
outletTwoReboot TRAP-TYPE
	ENTERPRISE xytronix
	DESCRIPTION
					"Outlet two reboot."
	::= 116

analogOne TRAP-TYPE
	ENTERPRISE xytronix
	DESCRIPTION
					"Analog one alarm."
	::= 120
	
analogTwo TRAP-TYPE
	ENTERPRISE xytronix
	DESCRIPTION
					"Analog two alarm."
	::= 121
	
analogThree TRAP-TYPE
	ENTERPRISE xytronix
	DESCRIPTION
					"Analog three alarm."
	::= 122
	
analogFour TRAP-TYPE
	ENTERPRISE xytronix
	DESCRIPTION
					"Analog four alarm."
	::= 123
	
analogFive TRAP-TYPE
	ENTERPRISE xytronix
	DESCRIPTION
					"Analog five alarm."
	::= 124
	
analogSix TRAP-TYPE
	ENTERPRISE xytronix
	DESCRIPTION
					"Analog six alarm."
	::= 125
	
analogSeven TRAP-TYPE
	ENTERPRISE xytronix
	DESCRIPTION
					"Analog seven alarm."
	::= 126
	
analogEight TRAP-TYPE
	ENTERPRISE xytronix
	DESCRIPTION
					"Analog eight alarm."
	::= 127
	

frequencyOne TRAP-TYPE
	ENTERPRISE xytronix
	DESCRIPTION
					"Frequency one alarm."
	::= 150
	
vin TRAP-TYPE
	ENTERPRISE xytronix
	DESCRIPTION
					"Vin alarm."
	::= 180

  
END
